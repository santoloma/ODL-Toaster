module toaster-app-config {
     yang-version 1;
     namespace "urn:opendaylight:params:xml:ns:yang:controller:toaster-app-config";
     prefix toaster-app-config;

     import toaster { prefix toaster; revision-date 2009-11-20; }

     description
       "Configuration for the Opendaylight toaster application.";

     revision "2016-05-03" {
         description
             "Initial revision.";
     }

     container toaster-app-config {
         leaf manufacturer {
             type toaster:DisplayString;
             default "Opendaylight";
         }

         leaf model-number {
             type toaster:DisplayString;
             default "Model 1 - Binding Aware";
         }

         leaf max-make-toast-tries {
             type uint16;
             default 2;
         }
     }
 }
